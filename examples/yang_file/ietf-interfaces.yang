module ietf-interfaces {

  yang-version 1;

  namespace
    "urn:ietf:params:xml:ns:yang:ietf-interfaces";

  prefix if;

  import ietf-yang-types {
    prefix yang;
  }
  import iana-if-type {
    prefix ianaift;
  }

  organization
    "IETF NETMOD (NETCONF Data Modeling Language) Working Group";

  contact
    "WG Web:   <http://tools.ietf.org/wg/netmod/>
   WG List:  <mailto:netmod@ietf.org>

   WG Chair: David Kessens
             <mailto:david.kessens@nsn.com>

   WG Chair: Juergen Schoenwaelder
             <mailto:j.schoenwaelder@jacobs-university.de>

   Editor:   Martin Bjorklund
             <mailto:mbj@tail-f.com>";

  description
    "This module contains a collection of YANG definitions for
   managing network interfaces.

   Copyright (c) 2012 IETF Trust and the persons identified as
   authors of the code.  All rights reserved.

   Redistribution and use in source and binary forms, with or
   without modification, is permitted pursuant to, and subject
   to the license terms contained in, the Simplified BSD License
   set forth in Section 4.c of the IETF Trust's Legal Provisions
   Relating to IETF Documents
   (http://trustee.ietf.org/license-info).

   This version of this YANG module is part of RFC XXXX; see
   the RFC itself for full legal notices.";

  revision "2012-09-05" {
    description "Initial revision.";
    reference
      "RFC XXXX: A YANG Data Model for Interface Management";

  }


  typedef interface-ref {
    type leafref {
      path
        "/if:interfaces/if:interface/if:name";
    }
    description
      "This type is used by data models that need to reference
     interfaces.";
  }

  feature if-mib {
    description
      "This feature indicates that the server implements IF-MIB.";
    reference
      "RFC 2863: The Interfaces Group MIB";

  }

  container interfaces {
    description "Interface parameters.";
    list interface {
      key "name";
      unique "type location";
      description
        "The list of interfaces on the device.";
      leaf name {
        type string;
        description
          "An arbitrary name for the interface.

         A device MAY restrict the allowed values for this leaf,
         possibly depending on the type and location.

         For example, if a device has a single array of 8 ethernet
         ports, the name might be restricted to be on the form
         'ethN', where N is an integer between '1' and '8'.

         This leaf MAY be mapped to ifName by an implementation.
         Such an implementation MAY restrict the allowed values for
         this leaf so that it matches the restrictions of ifName.
         If a NETCONF server that implements this restriction is
         sent a value that doesn't match the restriction, it MUST
         reply with an rpc-error with the error-tag
         'invalid-value'.";
        reference
          "RFC 2863: The Interfaces Group MIB - ifName";

      }

      leaf description {
        type string;
        description
          "A textual description of the interface.

         This leaf MAY be mapped to ifAlias by an implementation.
         Such an implementation MAY restrict the allowed values for
         this leaf so that it matches the restrictions of ifAlias.
         If a NETCONF server that implements this restriction is
         sent a value that doesn't match the restriction, it MUST
         reply with an rpc-error with the error-tag
         'invalid-value'.";
        reference
          "RFC 2863: The Interfaces Group MIB - ifAlias";

      }

      leaf type {
        type ianaift:iana-if-type;
        mandatory true;
        description
          "The type of the interface.

         When an interface entry is created, a server MAY
         initialize the type leaf with a valid value, e.g., if it
         is possible to derive the type from the name of the
         interface.";
        reference
          "RFC 2863: The Interfaces Group MIB - ifType";

      }

      leaf location {
        type string;
        description
          "The device-specific location of the interface of a
         particular type.  The format of the location string
         depends on the interface type and the device.

         If the interface's type represents a physical interface,
         this leaf MUST be set.

         For example, if a device has a single array of 8 ethernet
         ports, the location can be one of '1' to '8'.  As another
         example, if a device has N cards of M ports, the location
         can be on the form 'n/m'.

         When an interface entry is created, a server MAY
         initialize the location leaf with a valid value, e.g., if
         it is possible to derive the location from the name of
         the interface.";
      }

      leaf enabled {
        type boolean;
        default "true";
        description
          "The desired state of the interface.

         This leaf contains the configured, desired state of the
         interface.  Systems that implement the IF-MIB use the
         value of this leaf to set IF-MIB.ifAdminStatus to 'up' or
         'down' after an ifEntry has been initialized, as described
         in RFC 2863.";
        reference
          "RFC 2863: The Interfaces Group MIB - ifAdminStatus";

      }

      leaf oper-status {
        type enumeration {
          enum "up" {
            value 1;
            description
              "Ready to pass packets.";
          }
          enum "down" {
            value 2;
          }
          enum "testing" {
            value 3;
            description
              "In some test mode.  No operational packets can
             be passed.";
          }
          enum "unknown" {
            value 4;
            description
              "Status can not be determined
             for some reason.";
          }
          enum "dormant" {
            value 5;
          }
          enum "not-present" {
            value 6;
            description
              "Some component is missing.";
          }
          enum "lower-layer-down" {
            value 7;
            description
              "Down due to state of lower-layer
             interface(s).";
          }
        }
        config false;
        description
          "The current operational state of the interface.

         If 'enabled' is 'false' then 'oper-status'
         should be 'down'.  If 'enabled' is changed to 'true'
         then 'oper-status' should change to 'up' if the interface
         is ready to transmit and receive network traffic; it
         should change to 'dormant' if the interface is waiting for
         external actions (such as a serial line waiting for an
         incoming connection); it should remain in the 'down' state
         if and only if there is a fault that prevents it from
         going to the 'up' state; it should remain in the
         'not-present' state if the interface has missing
         (typically, hardware) components.";
        reference
          "RFC 2863: The Interfaces Group MIB - ifOperStatus";

      }

      leaf last-change {
        type yang:date-and-time;
        config false;
        description
          "The time the interface entered its current operational
         state.  If the current state was entered prior to the
         last re-initialization of the local network management
         subsystem, then this node is not present.";
        reference
          "RFC 2863: The Interfaces Group MIB - ifLastChange";

      }

      leaf if-index {
        if-feature if-mib;
        type int32 {
          range "1..2147483647";
        }
        config false;
        description
          "The ifIndex value for the ifEntry represented by this
         interface.

         Media-specific modules must specify how the type is
         mapped to entries in the ifTable.";
        reference
          "RFC 2863: The Interfaces Group MIB - ifIndex";

      }

      leaf mtu {
        type uint32;
        description
          "The size, in octets, of the largest packet that the
         interface can send and receive.  This node might not be
         valid for all interface types.

         Media-specific modules must specify any restrictions on
         the mtu for their interface type.";
        reference
          "RFC 2863: The Interfaces Group MIB - ifMtu";

      }

      leaf link-up-down-trap-enable {
        if-feature if-mib;
		default "enabled";  
        type enumeration {
          enum "enabled" {
            value 1;
          }
          enum "disabled" {
            value 2;
          }
		
        }
		
        description
          "Indicates whether linkUp/linkDown SNMP notifications
         should be generated for this interface.

         If this node is not configured, the value 'enabled' is
         operationally used by the server for interfaces which do
         not operate on top of any other interface (i.e., there are
         no 'lower-layer-if' entries), and 'disabled' otherwise.";
        reference
          "RFC 2863: The Interfaces Group MIB -
          	  ifLinkUpDownTrapEnable";

      }

      leaf phys-address {
        type yang:phys-address;
        config false;
        description
          "The interface's address at its protocol sub-layer.  For
        example, for an 802.x interface, this object normally
        contains a MAC address.  The interface's media-specific
        modules must define the bit and byte ordering and the
        format of the value of this object.  For interfaces that do
        not have such an address (e.g., a serial line), this node
        is not present.";
        reference
          "RFC 2863: The Interfaces Group MIB - ifPhysAddress";

      }

      leaf-list higher-layer-if {
        type interface-ref;
        config false;
        description
          "A list of references to interfaces layered on top of this
         interface.";
        reference
          "RFC 2863: The Interfaces Group MIB - ifStackTable";

      }

      leaf-list lower-layer-if {
        type interface-ref;
        config false;
        description
          "A list of references to interfaces layered underneath this
         interface.";
        reference
          "RFC 2863: The Interfaces Group MIB - ifStackTable";

      }

      leaf speed {
        type yang:gauge64;
        units "bits / second";
        description
          "An estimate of the interface's current bandwidth in bits
           per second.  For interfaces which do not vary in
           bandwidth or for those where no accurate estimation can
           be made, this node should contain the nominal bandwidth.
           For interfaces that has no concept of bandwidth, this
           node is not present.";
        reference
          "RFC 2863: The Interfaces Group MIB -
          	  ifSpeed, ifHighSpeed";

      }

      container statistics {
        config false;
        description
          "A collection of interface-related statistics objects.";
        leaf discontinuity-time {
          type yang:date-and-time;
          description
            "The time on the most recent occasion at which any one or
           more of this interface's counters suffered a
           discontinuity.  If no such discontinuities have occurred
           since the last re-initialization of the local management
           subsystem, then this node contains the time the local
           management subsystem re-initialized itself.";
        }

        leaf in-octets {
          type yang:counter64;
          description
            "The total number of octets received on the interface,
           including framing characters.

           Discontinuities in the value of this counter can occur
           at re-initialization of the management system, and at
           other times as indicated by the value of
           'discontinuity-time'.";
          reference
            "RFC 2863: The Interfaces Group MIB - ifHCInOctets";

        }

        leaf in-unicast-pkts {
          type yang:counter64;
          description
            "The number of packets, delivered by this sub-layer to a
           higher (sub-)layer, which were not addressed to a
           multicast or broadcast address at this sub-layer.

           Discontinuities in the value of this counter can occur
           at re-initialization of the management system, and at
           other times as indicated by the value of
           'discontinuity-time'.";
          reference
            "RFC 2863: The Interfaces Group MIB - ifHCInUcastPkts";

        }

        leaf in-broadcast-pkts {
          type yang:counter64;
          description
            "The number of packets, delivered by this sub-layer to a
           higher (sub-)layer, which were addressed to a broadcast
           address at this sub-layer.

           Discontinuities in the value of this counter can occur
           at re-initialization of the management system, and at
           other times as indicated by the value of
           'discontinuity-time'.";
          reference
            "RFC 2863: The Interfaces Group MIB -
            	  ifHCInBroadcastPkts";

        }

        leaf in-multicast-pkts {
          type yang:counter64;
          description
            "The number of packets, delivered by this sub-layer to a
           higher (sub-)layer, which were addressed to a multicast
           address at this sub-layer.  For a MAC layer protocol,
           this includes both Group and Functional addresses.

           Discontinuities in the value of this counter can occur
           at re-initialization of the management system, and at
           other times as indicated by the value of
           'discontinuity-time'.";
          reference
            "RFC 2863: The Interfaces Group MIB -
            	  ifHCInMulticastPkts";

        }

        leaf in-discards {
          type yang:counter32;
          description
            "The number of inbound packets which were chosen to be
           discarded even though no errors had been detected to
           prevent their being deliverable to a higher-layer
           protocol.  One possible reason for discarding such a
           packet could be to free up buffer space.

           Discontinuities in the value of this counter can occur
           at re-initialization of the management system, and at
           other times as indicated by the value of
           'discontinuity-time'.";
          reference
            "RFC 2863: The Interfaces Group MIB - ifInDiscards";

        }

        leaf in-errors {
          type yang:counter32;
          description
            "For packet-oriented interfaces, the number of inbound
           packets that contained errors preventing them from being
           deliverable to a higher-layer protocol.  For character-
           oriented or fixed-length interfaces, the number of
           inbound transmission units that contained errors
           preventing them from being deliverable to a higher-layer
           protocol.

           Discontinuities in the value of this counter can occur
           at re-initialization of the management system, and at
           other times as indicated by the value of
           'discontinuity-time'.";
          reference
            "RFC 2863: The Interfaces Group MIB - ifInErrors";

        }

        leaf in-unknown-protos {
          type yang:counter32;
          description
            "For packet-oriented interfaces, the number of packets
           received via the interface which were discarded because
           of an unknown or unsupported protocol.  For
           character-oriented or fixed-length interfaces that
           support protocol multiplexing the number of transmission
           units received via the interface which were discarded
           because of an unknown or unsupported protocol.  For any
           interface that does not support protocol multiplexing,
           this counter is not present.

           Discontinuities in the value of this counter can occur
           at re-initialization of the management system, and at
           other times as indicated by the value of
           'discontinuity-time'.";
          reference
            "RFC 2863: The Interfaces Group MIB - ifInUnknownProtos";

        }

        leaf out-octets {
          type yang:counter64;
          description
            "The total number of octets transmitted out of the
           interface, including framing characters.

           Discontinuities in the value of this counter can occur
           at re-initialization of the management system, and at
           other times as indicated by the value of
           'discontinuity-time'.";
          reference
            "RFC 2863: The Interfaces Group MIB - ifHCOutOctets";

        }

        leaf out-unicast-pkts {
          type yang:counter64;
          description
            "The total number of packets that higher-level protocols
           requested be transmitted, and which were not addressed
           to a multicast or broadcast address at this sub-layer,
           including those that were discarded or not sent.

           Discontinuities in the value of this counter can occur
           at re-initialization of the management system, and at
           other times as indicated by the value of
           'discontinuity-time'.";
          reference
            "RFC 2863: The Interfaces Group MIB - ifHCOutUcastPkts";

        }

        leaf out-broadcast-pkts {
          type yang:counter64;
          description
            "The total number of packets that higher-level protocols
           requested be transmitted, and which were addressed to a
           broadcast address at this sub-layer, including those
           that were discarded or not sent.

           Discontinuities in the value of this counter can occur
           at re-initialization of the management system, and at
           other times as indicated by the value of
           'discontinuity-time'.";
          reference
            "RFC 2863: The Interfaces Group MIB -
            	  ifHCOutBroadcastPkts";

        }

        leaf out-multicast-pkts {
          type yang:counter64;
          description
            "The total number of packets that higher-level protocols
           requested be transmitted, and which were addressed to a
           multicast address at this sub-layer, including those
           that were discarded or not sent.  For a MAC layer
           protocol, this includes both Group and Functional
           addresses.

           Discontinuities in the value of this counter can occur
           at re-initialization of the management system, and at
           other times as indicated by the value of
           'discontinuity-time'.";
          reference
            "RFC 2863: The Interfaces Group MIB -
            	  ifHCOutMulticastPkts";

        }

        leaf out-discards {
          type yang:counter32;
          description
            "The number of outbound packets which were chosen to be
           discarded even though no errors had been detected to
           prevent their being transmitted.  One possible reason
           for discarding such a packet could be to free up buffer
           space.

           Discontinuities in the value of this counter can occur
           at re-initialization of the management system, and at
           other times as indicated by the value of
           'discontinuity-time'.";
          reference
            "RFC 2863: The Interfaces Group MIB - ifOutDiscards";

        }

        leaf out-errors {
          type yang:counter32;
          description
            "For packet-oriented interfaces, the number of outbound
           packets that could not be transmitted because of errors.
           For character-oriented or fixed-length interfaces, the
           number of outbound transmission units that could not be
           transmitted because of errors.

           Discontinuities in the value of this counter can occur
           at re-initialization of the management system, and at
           other times as indicated by the value of
           'discontinuity-time'.";
          reference
            "RFC 2863: The Interfaces Group MIB - ifOutErrors";

        }
      }  // container statistics
    }  // list interface
  }  // container interfaces
}  // module ietf-interfaces
